KEMAlgorithmInformation-2023
    { iso(1) identified-organization(3) dod(6) internet(1) security(5)
      mechanisms(5) pkix(7) id-mod(0)
      id-mod-kemAlgorithmInformation-2023(109) }

DEFINITIONS EXPLICIT TAGS ::=

BEGIN

IMPORTS
    ParamOptions, PUBLIC-KEY
    FROM AlgorithmInformation-2009
        { iso(1) identified-organization(3) dod(6) internet(1) security(5)
          mechanisms(5) pkix(7) id-mod(0)
          id-mod-algorithmInformation-02(58) } ;

KEM-ALGORITHM ::= CLASS {
    &id             OBJECT IDENTIFIER UNIQUE,
    &Params         OPTIONAL,
    &paramPresence  ParamOptions DEFAULT absent,
    &SharedSecretLen INTEGER OPTIONAL,
    &PublicKeySet   PUBLIC-KEY OPTIONAL
} WITH SYNTAX {
    IDENTIFIER &id
    [PARAMS [TYPE &Params] ARE &paramPresence]
    [SHARED SECRET LENGTH &SharedSecretLen]
    [PUBLIC KEYS &PublicKeySet]
}

END
